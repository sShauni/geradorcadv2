Imports System.Collections.Generic
Imports System.Text.RegularExpressions
Imports Inventor

Public Class FixadorInfo
    Public PartNumber As String
    Public Norma As String
    Public Tipo As String
    Public Descricao As String
    Public Diametro As String
    Public Comprimento As String
    Public Quantidade As Integer
    
    Public Sub New()
        Quantidade = 0
    End Sub
End Class

Sub Main()
    If ThisApplication.ActiveDocument.DocumentType <> kAssemblyDocumentObject Then
        MessageBox.Show("Execute em uma Montagem (IAM).", "Erro")
        Exit Sub
    End If

    Dim oAsmDoc As AssemblyDocument = ThisApplication.ActiveDocument
    Dim listaFixadores As New Dictionary(Of String, FixadorInfo)
    
    TraverseAssembly(oAsmDoc.ComponentDefinition.Occurrences, listaFixadores)
    
    If listaFixadores.Count = 0 Then
        MessageBox.Show("Nenhum fixador encontrado.", "Aviso")
        Exit Sub
    End If
    
    ExportarParaExcel(listaFixadores)
End Sub

Sub TraverseAssembly(Occurrences As ComponentOccurrences, ByRef lista As Dictionary(Of String, FixadorInfo))
    For Each occ As ComponentOccurrence In Occurrences
        If occ.Suppressed Then Continue For
        
        If occ.DefinitionDocumentType = kAssemblyDocumentObject Then
            TraverseAssembly(occ.SubOccurrences, lista)
        ElseIf occ.DefinitionDocumentType = kPartDocumentObject Then
            If occ.Definition.IsContentMember Then
                ProcessarPeca(occ, lista)
            End If
        End If
    Next
End Sub

Sub ProcessarPeca(occ As ComponentOccurrence, ByRef lista As Dictionary(Of String, FixadorInfo))
    Try
        Dim doc As Document = occ.Definition.Document
        Dim props As PropertySets = doc.PropertySets
        Dim partNumber As String = ""
        
        Try
            partNumber = props("Design Tracking Properties").Item("Part Number").Value
        Catch
            partNumber = occ.Name
        End Try

        If lista.ContainsKey(partNumber) Then
            lista(partNumber).Quantidade += 1
        Else
            Dim novoFix As New FixadorInfo
            novoFix.PartNumber = partNumber
            novoFix.Quantidade = 1
            
            ' --- Propriedades de Texto ---
            novoFix.Descricao = GetProp(props, "Design Tracking Properties", "Description")
            novoFix.Norma = GetProp(props, "Design Tracking Properties", "Standard")
            If novoFix.Norma = "-" Or novoFix.Norma = "" Then novoFix.Norma = GetProp(props, "Design Tracking Properties", "Authority")
            novoFix.Tipo = GetProp(props, "Summary Information", "Title")
            
            ' --- Extração de Parâmetros (O Segredo está aqui) ---
            Dim reqParams As Parameters = occ.Definition.Parameters
            
            ' 1. Busca DIAMETRO
            Dim sDiam As String = "-"
            ' NLG e NND são os padrões modernos da ISO no Inventor
            Dim paramDnames As String() = {"NND", "d", "D", "Thread1_NominalDiameter", "NominalDiameter", "SIZE", "G"}
            For Each nome In paramDnames
                If TryGetParam(reqParams, nome, sDiam) Then Exit For
            Next
            
            ' 2. Busca COMPRIMENTO (Lista expandida)
            Dim sComp As String = "-"
            Dim paramLnames As String() = {"NLG", "NominalLength", "B_L", "L", "l", "LG", "Length", "OAL", "S_L", "p1"}
            
            Dim achouComp As Boolean = False
            For Each nome In paramLnames
                If TryGetParam(reqParams, nome, sComp) Then 
                    achouComp = True
                    Exit For
                End If
            Next
            
            ' --- PLANO B: Se não achou nos parâmetros, tenta extrair da DESCRIÇÃO ---
            If Not achouComp Or sComp = "-" Or sComp = "0" Then
                sComp = ExtrairComprimentoDaDescricao(novoFix.Descricao)
            End If
            
            novoFix.Diametro = sDiam
            novoFix.Comprimento = sComp
            
            lista.Add(partNumber, novoFix)
        End If
    Catch
    End Try
End Sub

' Função Inteligente para ler "M8x30" e devolver "30"
Function ExtrairComprimentoDaDescricao(desc As String) As String
    Try
        ' Procura por padrão "x Número" ou "xNúmero"
        ' Regex explica: procure 'x' ou 'X', seguido de espaço opcional, seguido de dígitos
        Dim padrao As String = "[xX]\s*(\d+)"
        Dim match As Match = Regex.Match(desc, padrao)
        
        If match.Success Then
            Return match.Groups(1).Value ' Retorna apenas o número capturado
        End If
        Return "-"
    Catch
        Return "-"
    End Try
End Function

Sub ExportarParaExcel(lista As Dictionary(Of String, FixadorInfo))
    Dim oExcelApp As Object = Nothing
    Dim oWorkbook As Object = Nothing
    Dim oSheet As Object = Nothing
    
    Try
        oExcelApp = CreateObject("Excel.Application")
        oExcelApp.Visible = True
        oWorkbook = oExcelApp.Workbooks.Add
        oSheet = oWorkbook.Sheets(1)
        
        ' Cabeçalho
        Dim headers() As String = {"Item", "Norma", "Tipo", "Diâmetro", "Comprimento", "Qtd", "Descrição Completa"}
        For i As Integer = 0 To headers.Length - 1
            oSheet.Cells(1, i + 1).Value = headers(i)
        Next
        
        Dim headerRange As Object = oSheet.Range("A1:G1")
        headerRange.Font.Bold = True
        headerRange.Interior.Color = 14277081 
        
        Dim row As Integer = 2
        Dim itemNum As Integer = 1
        
        Dim sortedKeys As List(Of String) = New List(Of String)(lista.Keys)
        sortedKeys.Sort()

        For Each key As String In sortedKeys
            Dim fix As FixadorInfo = lista(key)
            oSheet.Cells(row, 1).Value = itemNum
            oSheet.Cells(row, 2).Value = fix.Norma
            oSheet.Cells(row, 3).Value = fix.Tipo
            oSheet.Cells(row, 4).Value = fix.Diametro
            oSheet.Cells(row, 5).Value = fix.Comprimento
            oSheet.Cells(row, 6).Value = fix.Quantidade
            oSheet.Cells(row, 7).Value = fix.Descricao
            row += 1
            itemNum += 1
        Next
        
        Dim lastRow As Integer = row - 1
        If lastRow >= 2 Then
            Dim dataRange As Object = oSheet.Range("A1:G" & lastRow)
            dataRange.Borders.LineStyle = 1 
            oSheet.Columns("A").HorizontalAlignment = -4108 
            oSheet.Columns("D").HorizontalAlignment = -4108
            oSheet.Columns("E").HorizontalAlignment = -4108
            oSheet.Columns("F").HorizontalAlignment = -4108
            oSheet.Columns.AutoFit
        End If
        
    Catch ex As Exception
        MessageBox.Show("Erro Excel: " & ex.Message)
    End Try
End Sub

Function GetProp(props As PropertySets, setNames As String, propName As String) As String
    Try
        Dim val As Object = props(setNames).Item(propName).Value
        If val Is Nothing Then Return "-"
        Return val.ToString()
    Catch
        Return "-"
    End Try
End Function

Function TryGetParam(params As Parameters, paramName As String, ByRef result As String) As Boolean
    Try
        Dim p As Parameter = params.Item(paramName)
        result = p.Expression 
        If String.IsNullOrEmpty(result) Then result = p.Value.ToString("0.##")
        result = result.Replace("ul", "") 
        Return True
    Catch
        Return False
    End Try
End Function
